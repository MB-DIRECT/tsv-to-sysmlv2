// Generated by tsv_to_sysmlv2.py (dialect: pilot) from Homegrown_Export.tsv
// TODO-MIGRATE comments mark constructs needing a human pass;
// the companion .xlsx lists every non-migrated element/property/diagram.
package Homegrown_ {
    package Homegrown_Example1 {
        part def Homegrown_Block {
            port p1;
            part homegrown_Block2 : Homegrown_Block2;
            attribute value1 : Homegrown_Example3::Homegrown_valueType;
        }
        part def Homegrown_Block2 {
            port p1;
        }
        connection def __unnamed1 {
            end homegrown_Block2 : Homegrown_Block2; // aggregation: composite
            end end1 : Homegrown_Block;
        }
        item def Homegrown_signal;
        // DIAGRAM (not migrated): Homegrown_Example1  [Diagram]
    }
    package Homegrown_Example3 {
        attribute def Homegrown_valueType;
    }
    package Homegrown_Example2 {
        action def Homegrown_Example2 {
            // TODO-MIGRATE Activity Partition: no automatic v2 mapping
            // TODO-MIGRATE Activity Partition: no automatic v2 mapping
            // DIAGRAM (not migrated): Homegrown_Example2  [Diagram]
            action Homegrown_cba1 {
                out output : Homegrown_Example1::Homegrown_signal;
            }
            action Homegrown_cba2 {
                in input;
            }
            action __unnamed2; // was SysML 1.7 Initial Node
            first start then __unnamed2;
            merge __unnamed3;
            action __unnamed4; // was SysML 1.7 Activity Final Node
            first __unnamed4 then done;
            succession flow from Homegrown_cba1.output to Homegrown_cba2.input;
            // TODO-MIGRATE Control Flow: edge 'Homegrown_Example2' -> 'Homegrown_cba1' references undeclared/unnamed nodes (pin, initial, final...)
            // TODO-MIGRATE Control Flow: edge 'Homegrown_cba1' -> 'Homegrown_Example2' references undeclared/unnamed nodes (pin, initial, final...)
            // TODO-MIGRATE Control Flow: edge 'Homegrown_cba2' -> 'Homegrown_Example2' references undeclared/unnamed nodes (pin, initial, final...)
            // TODO-MIGRATE Control Flow: edge 'Homegrown_Example2' -> 'Homegrown_Example2' references undeclared/unnamed nodes (pin, initial, final...)
        }
    }
}
package 'MD Customization for ViewsViewpoints' {
    package customizations {
        part def Viewpoint; // was plain UML Class
        part def View { // was plain UML Class
            attribute 'Exposed Elements' [0..*]; // TODO-MIGRATE type was UML Standard Profile::UML2 Metamodel::Element
        }
        part def Conform; // was plain UML Class
        part def Expose; // was plain UML Class
        part def Stakeholder; // was plain UML Class
    }
}
